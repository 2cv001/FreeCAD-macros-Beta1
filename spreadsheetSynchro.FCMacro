#!/usr/bin/env python
# -*- coding: utf-8 -*-
# ========================================================================
# Macro spreadsheetSynchro.FCMacro
# ========================================================================
# principe : placer une formule du style @Sketch.Constraints.disty dans des cellule d'un spreadsheet
# sélectionnez les celulles en question
# lancez la fonction
# la macro ira chercher les valeurs dans la contrainte nommée disty du sketch
# et la placera dans la cellule à gauche de la formule
# fonctionne aussi pour un autre spreadsheet avec une formule du style @Spreadsheet.aliasDuneCellule

__Name__   = "spreadsheet Synchro"
__Comment__ =""
__Author__ = "2cv001"
__Title__   = "Macro spreadsheetSynchro"
__Date__    = "2024/01/22"    #YYYY/MM/DD 15:04 Béta
__Version__ = __Date__

# https://forum.freecad.org/viewtopic.php?t=84527


import FreeCAD
from PySide import QtGui

def get_previous_column(column):
    column = list(column)
    for i in range(len(column)-1, -1, -1):
        if column[i] != 'A':
            column[i] = chr(ord(column[i]) - 1)
            break
        else:
            column[i] = 'Z' if i != 0 else ''
    
    return ''.join(column)

def get_next_column(column):
    column = list(column)

    for i in range(len(column)-1, -1, -1):
        if column[i] != 'Z':
            column[i] = chr(ord(column[i]) + 1)
            break
        else:
            column[i] = 'A' if i != 0 else 'AA'    
    return ''.join(column)
    
def get_column(cell):
    column = ''.join([c for c in cell if not c.isdigit()])
    return column 
    
def get_left_cell(cell):
    column, row = re.findall(r"([A-Z]+)|([0-9]+)", cell)
    column = list(column[0])

    for i in range(len(column)-1, -1, -1):
        if column[i] != 'A':
            column[i] = chr(ord(column[i]) - 1)
            break
        else:
            column[i] = 'Z' if i != 0 else ''
    
    return ''.join(column) + ''.join(row)


# principe : placer une formule du style @Sketch.Constraints.disty dans des cellule d'un spreadsheet
# sélectionnez les celulles en question
# lancez la fonction
# la macro ira chercher les valeurs dans la contrainte nommée disty du sketch
# et la placera dans la cellule à gauche de la formule
# fonctionne aussi pour un autre spreadsheet avec une formule du style @Spreadsheet.aliasDuneCellule

def spreadsheetSynchro(cells):
    # Obtenez le document actif
    doc = FreeCAD.ActiveDocument
    mySpreadsheet = Gui.ActiveDocument.ActiveView.getSheet()


    for cell_name in cells:
        column = cell_name[0]
        if column=='A' :
            print('colonne A est une valeur non possible')
            return

        # Obtenez la formule de la cellule
        formula = mySpreadsheet.getContents(cell_name)

        formula = formula[1:]         # Supprimer le ' du début
        if not formula.startswith('@'):
            continue
        formula = formula[1:]   # on supprime le @ du début 


        # Analyser la formule pour obtenir le nom de la contrainte
        parts = formula.split('.')
        if len(parts) < 2  :
            continue

        objectName = parts[0]
        
        # l'objet à syncroniser est un Sketch
        if App.ActiveDocument.getObject(objectName).TypeId=='Sketcher::SketchObject' :
            constraint_name = parts[2]
            sketch = App.ActiveDocument.getObject(objectName)
            # Obtenez la contrainte du Sketch
            constraint = None
            for c in sketch.Constraints:
                if c.Name == constraint_name:
                    constraint = c
                    break
            if constraint is None:
                print(f"La contrainte {constraint_name} n'a pas été trouvée dans le Sketch.")
                continue
            value = constraint.Value

        # l'objet à syncroniser est un Spreadsheet            
        if App.ActiveDocument.getObject(objectName).TypeId=='Spreadsheet::Sheet' :
            spreadsheet = App.ActiveDocument.getObject(objectName)
            alias = parts[1] # un alias ou 'C1'
            value = App.ActiveDocument.getObject(objectName).getContents(alias)       
        # Mise à jour de la cellule à gauche avec la valeur de la contrainte


        mySpreadsheet.set(get_left_cell(cell_name), str(value))
        
    # Recalculez le document pour mettre à jour l'affichage
    doc.recompute()



aw = Gui.getMainWindow().centralWidget().activeSubWindow() # Store the active window      
# To get list of all selected cells
sel_items = aw.widget().findChild(QtGui.QTableView).selectedIndexes() 
tabCells=[]
cellName = lambda r,c:'{}{}{}'.format(chr(c//26 + 64) if c//26 > 0 else '', chr(c%26 + 65), r + 1)
for item in sel_items: # The selected cells are scanned
            tabCells.append( cellName(item.row(), item.column())) # We retrieve the cell ID in tabCells 
print('tabCells',tabCells)
spreadsheetSynchro(tabCells)
